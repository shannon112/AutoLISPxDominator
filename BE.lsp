(defun c:be( / ip d r r2 a30 a p1 p2 e1 e2)
 (if (null roatate)(load "util.lsp"))
  (graphscr)(command "osnap" "none")
  (if (and (setq ip (getpoint "\nInput insertion point<exit>: "))
           (setq d (getdist ip "\nInput diameter of the bolt<exit>: "))
	   )
    	(progn
	  (drawbe ip d)
	 )
    )
  (princ)
);end-c:be()
;=========================================
(defun drawbe(ip d / r r2 a30 a p1 p2 e1 e2)
 (setq r (/ d 2.0)
       r2(* r 1.5)
       a30(/ pi 6.0)
       a(/ r2(cos a30))
       p1(polar ip (- a30) a)
       p2(polar ip a30 a)
       )
(setq e1 (entlast))
(command "circle" ip r2)
(command "polygon" 6 "E" p1 p2)
(setq e2 (entlast))
(rotate ip e1 e2 nil)
(princ)
);end_drawbe()
