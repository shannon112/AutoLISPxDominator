(defun c:sq ( / ip p2 p3 p4 th1 th2 len)
	(graphscr)
	(command "osnap" "none")
	(setq ip (getpoint "\n Input first point"))
	(setq p2 (getpoint ip "\n Input second point"))

	(setq len (distance ip p2)
		th1(angle ip p2)
	      	th2(+ th1 (/ pi 2.0))
	      	p3 (polar p2 th2 len)
	      	p4 (polar ip th2 len)	      	
	      )
	(command "line" ip p2 p3 p4 "c")
	(princ)
)
