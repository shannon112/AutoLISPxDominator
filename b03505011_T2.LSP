;================================================
;   T2.LSP --- 
;================================================
(defun c:t2( / ip s1 s2 s3 ip phi dlist d1 d2 n e1 e2)
(if (null c:trod)(load "trod.lsp"))
(if (null tan)(load "util.lsp"))
  (graphscr)(command "osnap" "none")
   (if (and (setq ip (getpoint "\nInput the insertion point <exit>: "))
            (princ "\nDia. 20 25 30 40 50")
            (setq d1 (getreal "\nInput the norminal diameter <exit>: "))
            (setq dlist (finddat "t2.dat" d1))
       );end-if-test
       (progn
         (setq k (nth 1 dlist)
               e (nth 2 dlist)
	       s (nth 3 dlist)
	       d4 (nth 4 dlist)
	       d5 (nth 5 dlist)
               n (last dlist)
         )
         (drawt2 ip d1 k e s d4 d5 n)
       );end-if-then
   );end-if
);end-c:ew()
;================================================
(defun drawt2( ip d1 k e s d4 d5 n / r1 r4 r5 c dth dth/2 dth/4 th th1 th2 th5 th6 p1 p2 p3 p4 p5 asinin asinout th78 th9x innerr th7 th8 th9 thx p7 p8 p9 px)
  (setq r1 (/ d1 2.0)
        r4 (/ d4 2.0)
        r5 (/ d5 2.0)
        c (- r5 r4)
        dth (/ (* 2.0 pi) n)
        dth/2 (/ dth 2.0)
        dth/4 (/ dth 4.0)
	asinin (asin (/ (/ s 2.0) r4))
	asinout (asin (/ (/ s 2.0) r5))
	th78 (atan (/ (/ s 2.0) (- (- d1 k) r1)))
	th9x (asin (/ (/ s 2.0) r1))
	innerr (sqrt (+ (expt (- r1 (- d1 k)) 2.0) (expt (/ s 2.0) 2.0)))
        th 0.0    ;--- initial position
  )
  (repeat n
    (setq th1 (- th dth/2)
          th2 (- th asinin)
          th3 (- th asinout)
	  th4 (+ th asinout)
          th5 (+ th asinin)
          th6 (+ th dth/2)  
          p1 (polar ip th1 r4)
	  p2 (polar ip th2 r4)
          p3 (polar ip th3 r5)
          p4 (polar ip th4 r5)
          p5 (polar ip th5 r4)
          p6 (polar ip th6 r4)
          th (+ th dth)
    )
    (command "arc" "c" ip p1 p2)
    (command "line" p2 p3 "")
    (command "arc" "c" ip p3 p4)
    (command "line" p4 p5 "")
    (command "arc" "c" ip p5 p6)
  );end-repeat
  ;(command "circle" ip r1)
  (setq th7 (- 0.0 th78)
          th8 (+ 0.0 th78)
          th9 (- 0.0 th9x)
	  thx (+ 0.0 th9x)
          p7 (polar ip th7 innerr)
          p8 (polar ip th8 innerr)
          p9 (polar ip th9 r1)
          px (polar ip thx r1)
  )
    (command "arc" "c" ip px p9)
    (command "line" p7 p8 "")
    (command "line" p7 px "")
    (command "line" p8 p9 "")
  ;(redraw)
  (princ)
);end-ew()
;================================================
