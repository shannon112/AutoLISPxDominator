(defun c:star ( / pc r e1 e2)
  (graphscr)
  (if (and (setq pc (getpoint "\nEnter the center point <exit>: "))
           (setq r (getdist pc "\nEnter the radius <exit>: "))
      )
      (progn
	(command "circle" pc r)
        (setq e1 (entlast))
        (drawstar pc r)
        (setq e2 (entlast))
        (if (null rotate) (load"util.lsp"))
        ;(rotate pc e1 e2 nil)
      )
  );end-if
  (redraw)(princ)
);end_c:star()
(defun drawstar(pc r / p0 p1 p2 p3 p4 p5 p6 p7 p8 p9 p10 th dth)
  (setq dth (/ pi 0.5 5.0)
        th 0.0
        p1 (polar pc th r)
        th (+ th dth)
        p3 (polar pc th r)
        th (+ th dth)
        p5 (polar pc th r)
        th (+ th dth)
        p7 (polar pc th r)
        th (+ th dth)
        p9 (polar pc th r)
  )
  (setq
        p2 (inters p1 p5 p3 p9)
        p4 (inters p3 p7 p5 p1)
        p6 (inters p9 p5 p3 p7)
        p8 (inters p9 p5 p7 p1)
        p10(inters p1 p7 p3 p9)
  )
  (command "pline" p1 p2 p3 p4 p5 p6 p7 p8 p9 p10 "c")
  (princ)

)
;================================================
