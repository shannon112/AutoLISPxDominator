(defun c:bf( / ip d len dlist pitch)
 (if (null c:trod)(load "trod.lsp"))
  (if (null tan)(load "util.lsp"))
  (graphscr)(command "osnap" "none")
  (if (and (setq ip (getpoint "\nInput insertion point<exit>: "))
	(setq d (getreal "\nInput diameter of the bolt<exit>: "))
	(setq len (getdist ip "\nInput length of the bolt<exit>: "))
	(setq dlist (finddat "thread.dat" d))
	(setq pitch (cadr dlist))
	   )
  (progn
	(drawbf ip d len pitch)
    )
    );end if
  (princ)
)
;====================================================
(defun drawbf(ip d len pitch / r h r2 a b c c1 c2 c3 a30 a90 e1 e2 p1 p2 p3 p4 p4 p5 p6 p7 p8 p9 p10 p11 c1)
(setq r (/ d 2.0)
      h (/ (* d 2.0) 3.0)
      r2 (* r 1.5)
      a30 (/ pi 6.0)
      a (/ r2 (cos a30))
      b (/ a 2.0)
      c1 (* pitch (cos a30))
      c2 (- a r2)
      c3 (* c2 (tan a30))
       p1 (polar ip pi h)
      p2 (polar p1 0.0 c3)
       p3 (polar ip 0.0 (* len 0.3))
      p5 (polar ip 0.0 len)
       p4 (polar p5 pi c1)

      c (* a 0.75)
       a90 (/ pi 2.0)
      p6 (polar p1 a90 c)
       p7 (polar p1 (- a90) c)
      p8 (polar p2 a90 a)
       p9 (polar p2 (- a90) a)
      p10 (polar p2 a90 b)
       p11 (polar p2 (- a90) b)
      )
  (setq e1 (entlast))
  (command "arc" p8 p6 p10)
  (command "arc" p11 p7 p9)
  (command "arc" p10 p1 p11)
  ;---draw head
  (tu p1 p2 r2 a)
  (pm p2 ip a)
  (2pl p2 ip b)
  
  (2pl ip p3 r)
  (pr p3 p4 r)
  (tm p4 p5 r (- r c1))
  (setq cl (getvar "clayer"))
  (command "layer" "m" "dash" "")
  (2pl p3 p5 (- r c1))
  (command "layer" "s" cl "")
  (setq e2 (entlast))
  (if (null rotate)(load "rotate.lsp"))
  (rotate ip e1 e2 nil)
  (princ)
  );end_bf
